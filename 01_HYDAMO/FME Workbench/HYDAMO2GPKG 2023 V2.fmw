FME workspace HYDAMO2GPKG 2023 V2.fmw

Parameters:
- SourceDataset_FILEGDB_7 = U:\Projecten\OM\Oppervlaktewaterinstrumentarium\Oppervlaktewaterinstrumentarium.gdb   # Source Geodatabase
- DestDataset_ESRISHAPE_11 = U:\Gebruiker\keuljo01\HGK - NHI\INPUT\Lateral   # Destination Esri Shapefile Folder
- SourceDataset_ORACLE_SPATIAL_8 = raadpleeg@gprd   # Connection
- DestDataset_ESRISHAPE_12 = C:\HGK\INPUT\Dwarsprofiel   # Destination Esri Shapefile Folder
- SourceDataset_ORACLE_NONSPATIAL = raadpleeg@gprd   # Connection
- DestDataset_GML2_17 = D:\D-Hydamo\data\gml\stuwAM.gml   # Destination Geography Markup Language (GML) v2.1.2 File
- DestDataset_GML2_13 = D:\D-Hydamo\data\gml\brugAM.gml   # Destination Geography Markup Language (GML) v2.1.2 File
- DestDataset_GML2_19 = D:\D-Hydamo\data\gml\gemaalAM.gml   # Destination Geography Markup Language (GML) v2.1.2 File
- DestDataset_GML2_14 = D:\D-Hydamo\data\gml\onderspuierAM.gml   # Destination Geography Markup Language (GML) v2.1.2 File
- SourceDataset_FILEGDB = U:\Projecten\OM\Oppervlaktewaterinstrumentarium\Oppervlaktewaterinstrumentarium.gdb   # File Geodatabase
- SourceDataset_ORACLE_SPATIAL = raadpleeg@gprd   # Connection
- SourceDataset_GEODATABASE_FILE = U:\Projecten\OM\Ontsluiten_GIS_Data\Data\OM_data.gdb   # File Geodatabase
- SourceDataset_GEODATABASE_FILE_3 = U:\Projecten\OM\Ontsluiten_GIS_Data\Data\OM_data.gdb   # File Geodatabase
- DestDataset_OGCGEOPACKAGE = d:\MappenstructuurDHYDRO\00_Data\gpkg\AM.gpkg   # GeoPackage File
- DestDataset_OGCGEOPACKAGE_17 = d:\MappenstructuurDHYDRO\00_Data\gpkg\AM.gpkg   # GeoPackage File
- DestDataset_OGCGEOPACKAGE_13 = d:\MappenstructuurDHYDRO\00_Data\gpkg\AM.gpkg   # GeoPackage File
- DestDataset_OGCGEOPACKAGE_21 = d:\MappenstructuurDHYDRO\00_Data\gpkg\AM.gpkg   # GeoPackage File
- DestDataset_OGCGEOPACKAGE_15 = d:\MappenstructuurDHYDRO\00_Data\gpkg\AM.gpkg   # GeoPackage File
- DestDataset_OGCGEOPACKAGE_19 = d:\MappenstructuurDHYDRO\00_Data\gpkg\AM.gpkg   # GeoPackage File
- SourceDataset_ORACLE_SPATIAL_6 = raadpleeg@gprd   # Connection
- DestDataset_OGCGEOPACKAGE_23 = d:\MappenstructuurDHYDRO\00_Data\gpkg\AM.gpkg   # GeoPackage File
- DestDataset_OGCGEOPACKAGE_14 = d:\MappenstructuurDHYDRO\00_Data\gpkg\AM.gpkg   # GeoPackage File
- DestDataset_OGCGEOPACKAGE_16 = d:\MappenstructuurDHYDRO\00_Data\gpkg\AM.gpkg   # GeoPackage File
- DestDataset_OGCGEOPACKAGE_18 = d:\MappenstructuurDHYDRO\00_Data\gpkg\AM.gpkg   # GeoPackage File
- DestDataset_OGCGEOPACKAGE_20 = d:\MappenstructuurDHYDRO\00_Data\gpkg\AM.gpkg   # GeoPackage File
- DestDataset_OGCGEOPACKAGE_22 = d:\MappenstructuurDHYDRO\00_Data\gpkg\AM.gpkg   # GeoPackage File
- DestDataset_SHAPEFILE_2 = D:\D-HYDAMO\data\gis   # Destination Esri Shapefile Folder
- DestDataset_SHAPEFILE = D:\D-HYDAMO\data\gis   # Destination Esri Shapefile Folder
- SourceDataset_SHAPEFILE_13 = ""D:\D-HYDAMO\data\gis\Projectgrenzen\District Boven Aa\Goorloop.shp" "D:\D-HYDAMO\data\gis\Projectgrenzen\District Boven Aa\Vossenbeemd.shp""   # Source Esri Shapefile(s)
- SourceDataset_SHAPEFILE_7 = ""D:\D-HYDAMO\data\gis\Projectgrenzen\District Hertogswetering\Model_Gansoijen.shp" "D:\D-HYDAMO\data\gis\Projectgrenzen\District Hertogswetering\model_Groenendaal.shp" "D:\D-HYDAMO\data\gis\Projectgrenzen\District Hertogswetering\Model_Hertogswetering.shp""   # Source Esri Shapefile(s)
- SourceDataset_SHAPEFILE_15 = D:\D-HYDAMO\data\gis\HoogeRaam2.shp   # Source Esri Shapefile(s)
- SourceDataset_SHAPEFILE_14 = D:\D-HYDAMO\data\gis\Raamtest.shp   # Source Esri Shapefile(s)
- SourceDataset_SHAPEFILE = ""D:\D-HYDAMO\data\gis\Projectgrenzen\District Beneden Aa\Aa.shp" "D:\D-HYDAMO\data\gis\Projectgrenzen\District Beneden Aa\Biezenloop.shp" "D:\D-HYDAMO\data\gis\Projectgrenzen\District Beneden Aa\Groote Wetering.shp""   # Source Esri Shapefile(s)
- SourceDataset_ORACLE_SPATIAL_7 = raadpleeg@gprd   # Connection
- SourceDataset_SHAPEFILE_9 = D:\MappenstructuurDHYDRO\00_Data\gis\HoogeRaam.shp   # Source Esri Shapefile(s)

Readers:
- FILEGDB_1: FILEGDB from $(SourceDataset_FILEGDB_7)
- ORACLE_SPATIAL_1: ORACLE_SPATIAL from $(SourceDataset_ORACLE_SPATIAL_8) in Netherlands-RDNew-2008
- ORACLE_NONSPATIAL_1: ORACLE_NONSPATIAL from $(SourceDataset_ORACLE_NONSPATIAL)
- FILEGDB_2: FILEGDB from $(SourceDataset_FILEGDB)
- ORACLE_SPATIAL_2: ORACLE_SPATIAL from $(SourceDataset_ORACLE_SPATIAL)
- GEODATABASE_FILE_1: GEODATABASE_FILE from $(SourceDataset_GEODATABASE_FILE)
- GEODATABASE_FILE_2: GEODATABASE_FILE from $(SourceDataset_GEODATABASE_FILE_3)
- ORACLE_SPATIAL_3: ORACLE_SPATIAL from $(SourceDataset_ORACLE_SPATIAL_6)
- GEODATABASE_SDE_1: GEODATABASE_SDE
- GEODATABASE_SDE_2: GEODATABASE_SDE
- SHAPEFILE_1: SHAPEFILE from $(SourceDataset_SHAPEFILE)
- SHAPEFILE_2: SHAPEFILE from $(SourceDataset_SHAPEFILE_13)
- SHAPEFILE_3: SHAPEFILE from $(SourceDataset_SHAPEFILE_7)
- SHAPEFILE_8: SHAPEFILE from $(SourceDataset_SHAPEFILE_15)
- SHAPEFILE_10: SHAPEFILE from $(SourceDataset_SHAPEFILE_14)
- ORACLE_SPATIAL_5: ORACLE_SPATIAL from $(SourceDataset_ORACLE_SPATIAL_7)
- SHAPEFILE_5: SHAPEFILE from $(SourceDataset_SHAPEFILE_9)

Writers:
- ESRISHAPE_1: ESRISHAPE to $(DestDataset_ESRISHAPE_11)
- ESRISHAPE_2: ESRISHAPE to $(DestDataset_ESRISHAPE_12)
- GML2_1: GML2 to $(DestDataset_GML2_17)
- GML2_2: GML2 to $(DestDataset_GML2_13)
- GML2_3: GML2 to $(DestDataset_GML2_19)
- GML2_5: GML2 to $(DestDataset_GML2_14)
- OGCGEOPACKAGE_1: OGCGEOPACKAGE to $(DestDataset_OGCGEOPACKAGE) in Netherlands-RDNew-2008
- OGCGEOPACKAGE_2: OGCGEOPACKAGE to $(DestDataset_OGCGEOPACKAGE_17) in Netherlands-RDNew-2008
- OGCGEOPACKAGE_3: OGCGEOPACKAGE to $(DestDataset_OGCGEOPACKAGE_13) in Netherlands-RDNew-2008
- OGCGEOPACKAGE_4: OGCGEOPACKAGE to $(DestDataset_OGCGEOPACKAGE_21) in Netherlands-RDNew-2008
- OGCGEOPACKAGE_5: OGCGEOPACKAGE to $(DestDataset_OGCGEOPACKAGE_15) in Netherlands-RDNew-2008
- OGCGEOPACKAGE_6: OGCGEOPACKAGE to $(DestDataset_OGCGEOPACKAGE_19) in Netherlands-RDNew-2008
- OGCGEOPACKAGE_7: OGCGEOPACKAGE to $(DestDataset_OGCGEOPACKAGE_23) in Netherlands-RDNew-2008
- OGCGEOPACKAGE_8: OGCGEOPACKAGE to $(DestDataset_OGCGEOPACKAGE_14) in Netherlands-RDNew-2008
- OGCGEOPACKAGE_9: OGCGEOPACKAGE to $(DestDataset_OGCGEOPACKAGE_16) in Netherlands-RDNew-2008
- OGCGEOPACKAGE_10: OGCGEOPACKAGE to $(DestDataset_OGCGEOPACKAGE_18) in Netherlands-RDNew-2008
- OGCGEOPACKAGE_11: OGCGEOPACKAGE to $(DestDataset_OGCGEOPACKAGE_20) in Netherlands-RDNew-2008
- OGCGEOPACKAGE_12: OGCGEOPACKAGE to $(DestDataset_OGCGEOPACKAGE_22) in Netherlands-RDNew-2008
- SHAPEFILE_6: SHAPEFILE to $(DestDataset_SHAPEFILE)
- SHAPEFILE_7: SHAPEFILE to $(DestDataset_SHAPEFILE_2)

Note: Hier wordt de projectgrens van het model opgegeven.
Note: De BGT kan worden gebruikt om de waterlopen uit het 2D-rooster te knippen.
Note: De vispassages worden gebruik om de hydro_objects van technische vispassages te verwijderen, omdat er onvoldoende gegevens zijn om deze te gebruiken in D-HYDRO.
Junction
    -> Clipper_4 [CLIPPER]
    -> Clipper_3 [CLIPPER]
    -> Clipper_9 [CLIPPER]
    -> Clipper [CLIPPER]
    -> Clipper_8 [CLIPPER]
    -> Clipper_2 [CLIPPER]
    -> Clipper_5 [CLIPPER]
    -> Clipper_6 [CLIPPER]
    -> Clipper_7 [CLIPPER]
    -> Clipper_10 [CLIPPER]

Bookmark: Dwarsprofiel
PROFIELPUNTEN (reader ORACLE_NONSPATIAL_1)
    attributes: OBJECTID number(38,0), PROIDENT nvarchar(24), IWS_VOLGNR number(6,0), OSMOMSCH nvarchar(60), PBPSOORT nvarchar(100), IWS_HOOGTE number(7,3), IWS_AFSTAND number(12,3), X number, Y number
    -> VertexCreator
VertexCreator
    MEASURE_TYPE = Continuous
    MODE_NAME = Replace with Point
    XVAL = @Value(X)
    YVAL = @Value(Y)
    ZVAL = @Value(IWS_HOOGTE)
    -> CoordinateSystemSetter
CoordinateSystemSetter
    COORDSYS = Netherlands-RDNew-2008
    -> Clipper_8 [CLIPPEE]
Clipper_8
    BOUNDARY_CASES = Treat as Inside
    CLEANING_TOLERANCE = Automatic
    CLIPPED_ATTR = _clipped
    CLIP_TYPE = Multiple Clippers
    LINES_AS_SEGMENTS = No
    MEASURE_TYPE = Continuous
    MISSING_VAL_MODE = Compute
    PRESERVE_CLIPPEE_EXTENTS = No
    VAL_SOURCE = Clippee Only
    INSIDE -> Matcher_2
Matcher_2
    CHECK_COORDINATE_SYSTEMS = No
    CNT_ATTR = _match_id
    LENIENT_MATCH = No
    MATCH = 2D
    MATCHED -> Profielpunten_opdelen_in_waterbodem_en_slib_2
    NOT_MATCHED -> AttributeRenamer_9
Profielpunten_opdelen_in_waterbodem_en_slib_2: TestFilter
    DEFAULT_VALUE = <UNFILTERED>
    PASSED_TEST_GROUP_OUTPUT = FIRST
    TEST_LIST = "BOOL_OP,OR,COMPOSITE_TEST,""""""1"""""",TEST_CLAUSE,TEST @Value(OSMOMSCH) = Z1",Waterbodem,"BOOL_OP,OR,COMPOSITE_TEST,""""""1"""""",TEST_CLAUSE,TEST @Value(OSMOMSCH) = Z2",Slib
    Slib -> AttributeRenamer_9
AttributeRenamer_9
    ATTR_TABLE = RENAME_SET_DEFAULT IWS_VOLGNR > codevolgnummer
    MISSING_INPUT_ATTRS = REMOVE
    -> DuplicateFilter_2
DuplicateFilter_2
    INPUT_ORDERED_CHOICE = No
    KEYATTR = codevolgnummer PROIDENT
    UNIQUE -> NeighborFinder [BASE]
GW_PRO (reader ORACLE_SPATIAL_3)
    attributes: OBJECTID number(38,0), PRO_ID number(10,0), PRO_TYPE nvarchar(100), IPRKS_IPRKS_ID number(10,0), PROIDENT nvarchar(24), PROSOORT nvarchar(100), OPRDATOP timestamp(6), OSMOMSCH nvarchar(60), SE_ANNO_CAD_DATA blob
    -> Clipper_6 [CLIPPEE]
Clipper_6
    BOUNDARY_CASES = Treat as Inside
    CLEANING_TOLERANCE = Automatic
    CLIPPED_ATTR = _clipped
    CLIP_TYPE = Multiple Clippers
    LINES_AS_SEGMENTS = No
    MEASURE_TYPE = Continuous
    MISSING_VAL_MODE = Compute
    PRESERVE_CLIPPEE_EXTENTS = No
    VAL_SOURCE = Clippee Only
    INSIDE -> Tester_2
Tester_2
    BOOL_OP = AND
    TEST_CLAUSE:
      CASE_INSENSITIVE_TEST @Value(PROIDENT) LIKE %P%
      CASE_INSENSITIVE_TEST @Value(PROSOORT) = profiel oppervlaktewater
    TEST_MODE = CASE_INSENSITIVE_TEST
    PASSED -> AttributeCreator_nen3610id
AttributeCreator_nen3610id
    ATTR_TABLE = SET_TO nen3610id = @Value(PROIDENT)
    -> globalid
globalid: UUIDGenerator
    UUID_ATTR = globalid
    -> profielgroep (writer OGCGEOPACKAGE_6)
    -> AttributeRenamer_2
AttributeRenamer_2
    ATTR_TABLE = RENAME_SET_DEFAULT globalid > profielgroepid
    MISSING_INPUT_ATTRS = REMOVE
    -> UUIDGenerator_globalid
UUIDGenerator_globalid
    UUID_ATTR = globalid
    UUID_FORMAT = UUID_ONLY
    -> profiellijn (writer OGCGEOPACKAGE_7)
    -> AttributeRenamer_10
AttributeRenamer_10
    ATTR_TABLE = RENAME_SET_DEFAULT globalid > profiellijnid
    MISSING_INPUT_ATTRS = REMOVE
    -> FeatureMerger_2 [SUPPLIER]
Maaifrequentie2021 (reader GEODATABASE_FILE_2)
    attributes: OBJECTID_1 integer, CODE char(10), ONDERHOUDSCODE char(10), BOVENBREEDTE char(10), FREQUENCY integer, Shape_Length double
    -> NeighborFinder [CANDIDATE]
NeighborFinder
    ATTR_ACCUM_MODE = Merge Candidate
    ATTR_CONFLICT_RES = Use Base
    CANDIDATES_FIRST = No
    INSERT_VERTEX = No
    K = 1
    MEASURES_FROM_CANDIDATE = No
    MEASURE_TYPE = Continuous
    MODE = Bases and Candidates
    TREAT_POLYGON_AS = Lines
    MATCHED -> AttributeRemover_3
AttributeRemover_3
    REMOVE_ATTRS = _angle,_candidate_angle,_candidate_label_angle,_clipped,_closest_base_x,_closest_base_y,_closest_candidate_x,_closest_candidate_y,_distance,_match_id,CODE
    -> AttributeCreator_15
AttributeCreator_15
    ATTR_TABLE:
      SET_TO typeprofielcode = 4
      SET_TO typeruwheid = StricklerKs
      SET_TO ruwheidlaag = FME_CONDITIONAL:DEFAULT_VALUE'30'BOOL_OP;AND;COMPOSITE_TEST;1 AND 2;TEST @Value(FREQUENCY) = 0;TEST @Value(BOVENBREEDTE) = < 6 m'15'BOOL_OP;AND;COMPOSITE_TEST;1 AND 2;TEST @Value(FREQUENCY) = 1;TEST @Value(BOVENBREEDTE) = < 6 m'20'BOOL_OP;AND;COMPOSITE_TEST;1 AND 2;TEST @Value(FREQUENCY) = 2;TEST @Value(BOVENBREEDTE) = < 6 m'25'BOOL_OP;AND;COMPOSITE_TEST;1 AND 2;TEST @Value(FREQUENCY) = 3;TEST @Value(BOVENBREEDTE) = < 6 m'30'BOOL_OP;AND;COMPOSITE_TEST;1 AND 2;TEST @Value(FREQUENCY) = 4;TEST @Value(BOVENBREEDTE) = < 6 m'30'BOOL_OP;AND;COMPOSITE_TEST;1 AND 2;TEST @Value(FREQUENCY) >= 5;TEST @Value(BOVENBREEDTE) = < 6 m'30'BOOL_OP;AND;COMPOSITE_TEST;1 AND 2;TEST @Value(FREQUENCY) = 0;TEST @Value(BOVENBREEDTE) = 6 - 12 m'20'BOOL_OP;AND;COMPOSITE_TEST;1 AND 2;TEST @Value(FREQUENCY) = 1;TEST @Value(BOVENBREEDTE) = 6 - 12 m'25'BOOL_OP;AND;COMPOSITE_TEST;1 AND 2;TEST @Value(FREQUENCY) = 2;TEST @Value(BOVENBREEDTE) = 6 - 12 m'30'BOOL_OP;AND;COMPOSITE_TEST;1 AND 2;TEST @Value(FREQUENCY) = 3;TEST @Value(BOVENBREEDTE) = 6 - 12 m'30'BOOL_OP;AND;COMPOSITE_TEST;1 AND 2;TEST @Value(FREQUENCY) = 4;TEST @Value(BOVENBREEDTE) = 6 - 12 m'30'BOOL_OP;AND;COMPOSITE_TEST;1 AND 2;TEST @Value(FREQUENCY) >= 5;TEST @Value(BOVENBREEDTE) = 6 - 12 m'30'BOOL_OP;AND;COMPOSITE_TEST;1 AND 2;TEST @Value(FREQUENCY) = 0;TEST @Value(BOVENBREEDTE) = > 12 m'25'BOOL_OP;AND;COMPOSITE_TEST;1 AND 2;TEST @Value(FREQUENCY) = 1;TEST @Value(BOVENBREEDTE) = > 12 m'30'BOOL_OP;AND;COMPOSITE_TEST;1 AND 2;TEST @Value(FREQUENCY) = 2;TEST @Value(BOVENBREEDTE) = > 12 m'30'BOOL_OP;AND;COMPOSITE_TEST;1 AND 2;TEST @Value(FREQUENCY) = 3;TEST @Value(BOVENBREEDTE) = > 12 m'30'BOOL_OP;AND;COMPOSITE_TEST;1 AND 2;TEST @Value(FREQUENCY) = 4;TEST @Value(BOVENBREEDTE) = > 12 m'30'BOOL_OP;AND;COMPOSITE_TEST;1 AND 2;TEST @Value(FREQUENCY) >= 5;TEST @Value(BOVENBREEDTE) = > 12 m'30'FME_NUM_CONDITIONS19___
      SET_TO ruwheidhoog = FME_CONDITIONAL:DEFAULT_VALUE'15'BOOL_OP;AND;COMPOSITE_TEST;1 AND 2;TEST @Value(FREQUENCY) = 0;TEST @Value(BOVENBREEDTE) = < 6 m'5'BOOL_OP;AND;COMPOSITE_TEST;1 AND 2;TEST @Value(FREQUENCY) = 1;TEST @Value(BOVENBREEDTE) = < 6 m'10'BOOL_OP;AND;COMPOSITE_TEST;1 AND 2;TEST @Value(FREQUENCY) = 2;TEST @Value(BOVENBREEDTE) = < 6 m'15'BOOL_OP;AND;COMPOSITE_TEST;1 AND 2;TEST @Value(FREQUENCY) = 3;TEST @Value(BOVENBREEDTE) = < 6 m'20'BOOL_OP;AND;COMPOSITE_TEST;1 AND 2;TEST @Value(FREQUENCY) = 4;TEST @Value(BOVENBREEDTE) = < 6 m'25'BOOL_OP;AND;COMPOSITE_TEST;1 AND 2;TEST @Value(FREQUENCY) >= 5;TEST @Value(BOVENBREEDTE) = < 6 m'30'BOOL_OP;AND;COMPOSITE_TEST;1 AND 2;TEST @Value(FREQUENCY) = 0;TEST @Value(BOVENBREEDTE) = 6 - 12 m'10'BOOL_OP;AND;COMPOSITE_TEST;1 AND 2;TEST @Value(FREQUENCY) = 1;TEST @Value(BOVENBREEDTE) = 6 - 12 m'15'BOOL_OP;AND;COMPOSITE_TEST;1 AND 2;TEST @Value(FREQUENCY) = 2;TEST @Value(BOVENBREEDTE) = 6 - 12 m'20'BOOL_OP;AND;COMPOSITE_TEST;1 AND 2;TEST @Value(FREQUENCY) = 3;TEST @Value(BOVENBREEDTE) = 6 - 12 m'25'BOOL_OP;AND;COMPOSITE_TEST;1 AND 2;TEST @Value(FREQUENCY) = 4;TEST @Value(BOVENBREEDTE) = 6 - 12 m'30'BOOL_OP;AND;COMPOSITE_TEST;1 AND 2;TEST @Value(FREQUENCY) >= 5;TEST @Value(BOVENBREEDTE) = 6 - 12 m'30'BOOL_OP;AND;COMPOSITE_TEST;1 AND 2;TEST @Value(FREQUENCY) = 0;TEST @Value(BOVENBREEDTE) = > 12 m'15'BOOL_OP;AND;COMPOSITE_TEST;1 AND 2;TEST @Value(FREQUENCY) = 1;TEST @Value(BOVENBREEDTE) = > 12 m'20'BOOL_OP;AND;COMPOSITE_TEST;1 AND 2;TEST @Value(FREQUENCY) = 2;TEST @Value(BOVENBREEDTE) = > 12 m'25'BOOL_OP;AND;COMPOSITE_TEST;1 AND 2;TEST @Value(FREQUENCY) = 3;TEST @Value(BOVENBREEDTE) = > 12 m'30'BOOL_OP;AND;COMPOSITE_TEST;1 AND 2;TEST @Value(FREQUENCY) = 4;TEST @Value(BOVENBREEDTE) = > 12 m'30'BOOL_OP;AND;COMPOSITE_TEST;1 AND 2;TEST @Value(FREQUENCY) >= 5;TEST @Value(BOVENBREEDTE) = > 12 m'30'FME_NUM_CONDITIONS19___
      SET_TO codegerelateerdobject
      SET_TO code = @Value(PROIDENT)
      SET_TO nen3610id = @Value(PROIDENT)
    -> Sorter_2
Sorter_2
    SORT_PARM = code NATURAL ASCENDING codevolgnummer NATURAL ASCENDING
    SORTED -> UUIDGenerator_3
UUIDGenerator_3
    UUID_ATTR = globalid
    -> FeatureMerger_2 [REQUESTOR]
    -> AttributeRenamer_11
AttributeRenamer_11
    ATTR_TABLE = RENAME_SET_DEFAULT globalid > profielpuntid
    MISSING_INPUT_ATTRS = REMOVE
    -> ruwheidprofiel (writer OGCGEOPACKAGE_9)
FeatureMerger_2
    ATTR_ACCUM_MODE = Merge Supplier
    ATTR_CONFLICT_RES = Use Requestor
    IGNORE_NULLS = No
    JOIN_KEYS = @Value(PROIDENT) @Value(PROIDENT) AUTO
    MERGE_TYPE = Attributes Only
    PROCESS_DUPS = NO
    REJECT_NULL_MISSING_KEYS = No
    SUPPLIERS_FIRST = No
    MERGED -> profielpunt (writer OGCGEOPACKAGE_8)
profiellijn (writer OGCGEOPACKAGE_7)
    attributes: globalid text(200), profielgroepid text(200), nen3610id text(200)
UUIDGenerator_globalid_2
    UUID_ATTR = globalid
    UUID_FORMAT = UUID_ONLY
    -> profielpunt (writer OGCGEOPACKAGE_8)
    -> AttributeRenamer_profielpuntid
AttributeRenamer_profielpuntid
    ATTR_TABLE = RENAME_SET_DEFAULT globalid > profielpuntid
    MISSING_INPUT_ATTRS = REMOVE
    -> ruwheidprofiel (writer OGCGEOPACKAGE_9)
ruwheidprofiel (writer OGCGEOPACKAGE_9)
    attributes: code text(200), profielpuntid text(200), typeruwheid text(200), ruwheidhoog double, ruwheidlaag double, nen3610id text(200)
profielpunt (writer OGCGEOPACKAGE_8)
    attributes: code text(200), globalid text(200), profiellijnid text(200), codevolgnummer int, nen3610id text(200)
profielgroep (writer OGCGEOPACKAGE_6)
    attributes: globalid text(200), brugid text(200), stuwid text(200), nen3610id text(200)

Bookmark: Projectgebied
HoogeRaam (reader SHAPEFILE_5)
    attributes: CODE varchar(50), NAAM varchar(100), SOORTAFVOE varchar(100), WATERAFVOE long, OPPERVLAKT number(12,0), WS_AFVOERC double, AFVOERAANV varchar(38), ORDECODE varchar(100)
    -> Junction

Bookmark: BGT
waterdeel_v (reader GEODATABASE_SDE_2) [off]
    attributes: OBJECTID integer, BGTPLUSTYPE char(50), SUBTYPE smallint, IDENTIFICATIE char(255), STATUS char(10), OBJECTBEGINTIJD date, OBJECTEINDTIJD date, BRONHOUDER char(5), INONDERZOEK char(1), RELATIEVEHOOGTELIGGING range_domain(GeoBGT_relatieveHL0:smallint:0:0), TIJDSTIPREGISTRATIE date, EINDREGISTRATIE date, LV_PUBLICATIEDATUM date, BERICHT_ID char(128), BOR_ID char(50), GLOBALID globalid, CREATED_USER char(255), CREATED_DATE date, LAST_EDITED_USER char(255), LAST_EDITED_DATE date, SHAPE.AREA double, SHAPE.LEN double
    -> Tester_4 [off]
Tester_4 [off]
    BOOL_OP = OR
    TEST_CLAUSE = CASE_INSENSITIVE_TEST @Value(BGTPLUSTYPE) CONTAINS waterloop
    TEST_MODE = TEST
    PASSED -> Clipper_7 [CANDIDATE] [off]
Clipper_7 [off]
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> SpatialRelator_2 [Requestor] [off]
SpatialRelator_2 [off]
    AGGREGATE_HANDLING = Yes
    CALC_CARD = No
    CURVE_BOUNDARY_RULE_PARAM = Default Rule
    LIST_NAME = _relationships
    PREDICATES = INTERSECTS
    SUCCESS_ATTR = _related_suppliers
    -> Tester_5 [off]
Tester_5 [off]
    BOOL_OP = OR
    TEST_CLAUSE = TEST @Value(_related_suppliers) > 0
    TEST_MODE = TEST
    PASSED -> Dissolver [off]
Dissolver [off]
    ACCUM_INPUT_ATTRS = Use Attributes From One Feature
    CLEANING_TOLERANCE = Automatic
    CONNECT_Z_MODE = First Wins
    DEAGGREGATE_INPUT = Yes
    AREA -> bgt (writer SHAPEFILE_7) [off]
bgt (writer SHAPEFILE_7) [off]
    attributes: OBJECTID long

Bookmark: Vispassage
Note: Het waterlopenbestand wordt gebruikt om de hydro_objects een naam te geven zodat deze gegroepeerd kunnen worden. Dit is nodig voor de interpolatie over connection nodes zodat er veel minder dummyprofielen aangemaakt hoeven te worden.
VISPASSAGE (reader ORACLE_SPATIAL_5)
    attributes: OBJECTID number(38,0), CODE nvarchar(50), WS_SOORTVISPASSAGE nvarchar(100), WS_STUWHOOGTEBOVEN number(7,3), WS_AANTALTRAPPEN number(5,0), WS_AANLEGJAAR timestamp(6), OPMERKING nvarchar(250), STATUSLEGGERWATERSYSTEEM nvarchar(100), STATUSLEGGERWATERVEILIGHEID nvarchar(100), STATUSOBJECT nvarchar(100), RICHTING number(5,2), WS_INWINDATUM timestamp(6), VISPASSAGEID char(38), SE_ANNO_CAD_DATA blob
    -> Clipper_10 [CANDIDATE]
Clipper_10
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> Tester_7
Tester_7
    BOOL_OP = OR
    TEST_CLAUSE = TEST @Value(WS_SOORTVISPASSAGE) != bekkenvispassage
    TEST_MODE = TEST
    PASSED -> SpatialRelator_3 [Supplier]

Bookmark: Waterloop
HYDROOBJECTAGGREGATIE (reader ORACLE_SPATIAL_2)
    attributes: OBJECTID number(38,0), CODE nvarchar(50), NAAM nvarchar(50), STATUSOBJECT nvarchar(100), SE_ANNO_CAD_DATA blob, HYDROOBJECTGROEPERINGID char(38)
    -> AttributeRenamer
    -> Clipper_9 [CLIPPER]
AttributeRenamer
    ATTR_TABLE = RENAME_SET_DEFAULT CODE > naam
    MISSING_INPUT_ATTRS = REMOVE
    -> SpatialRelator [Supplier]
HYDROOBJECT (reader ORACLE_SPATIAL_1)
    attributes: OBJECTID number(38,0), CODE nvarchar(50), CATEGORIEOPPWATERLICHAAM nvarchar(100), SOORTOPPWATERKWANTITEIT nvarchar(100), OPMERKING nvarchar(250), STATUSLEGGERWATERSYSTEEM nvarchar(100), STATUSOBJECT nvarchar(100), KRWSTROMENDID char(38), SE_ANNO_CAD_DATA blob, HYDROOBJECTGROEPERINGID char(38), HYDROOBJECTID char(38)
    -> Clipper_9 [CLIPPEE]
Clipper_9
    BOUNDARY_CASES = Treat as Inside
    CLEANING_TOLERANCE = Automatic
    CLIPPED_ATTR = _clipped
    CLIP_TYPE = Multiple Clippers
    LINES_AS_SEGMENTS = No
    MEASURE_TYPE = Continuous
    MISSING_VAL_MODE = Compute
    PRESERVE_CLIPPEE_EXTENTS = No
    VAL_SOURCE = Clippee Only
    INSIDE -> Tester_6
Tester_6
    BOOL_OP = AND
    TEST_CLAUSE:
      TEST @Value(CATEGORIEOPPWATERLICHAAM) = primair
      TEST @Value(STATUSOBJECT) = gerealiseerd
    TEST_MODE = TEST
    PASSED -> SpatialRelator [Requestor]
    PASSED -> SpatialRelator_2 [Supplier]
SpatialRelator
    AGGREGATE_HANDLING = Yes
    ATTR_ACCUM_MODE = Merge Supplier
    ATTR_CONFLICT_RES = Use Requestor
    CALC_CARD = No
    CURVE_BOUNDARY_RULE_PARAM = Default Rule
    IGNORE_NULLS = Yes
    LIST_NAME = _relationships
    PREDICATES = WITHIN
    SUCCESS_ATTR = _related_suppliers
    -> NullAttributeMapper
NullAttributeMapper
    ATTRCHOICE = Selected Attributes
    ATTRLIST = naam
    NEW_VALUE = 0
    NULL_TREATMENT = New Value
    SOURCE_ATTR_VAL = Null
    -> AttributeRenamer_3
AttributeRenamer_3
    ATTR_TABLE:
      RENAME_SET_DEFAULT CODE > code
      RENAME_SET_DEFAULT HYDROOBJECTID > globalid
    MISSING_INPUT_ATTRS = REMOVE
    -> DuplicateFilter
DuplicateFilter
    INPUT_ORDERED_CHOICE = No
    KEYATTR = code
    UNIQUE -> AttributeCreator_3
AttributeCreator_3
    ATTR_TABLE = SET_TO nen3610id = @Value(code)
    -> SpatialRelator_3 [Requestor]
SpatialRelator_3
    AGGREGATE_HANDLING = Yes
    CALC_CARD = No
    CURVE_BOUNDARY_RULE_PARAM = Default Rule
    LIST_NAME = _relationships
    PREDICATES = INTERSECTS
    SUCCESS_ATTR = _related_suppliers
    -> Tester_8
Tester_8
    BOOL_OP = OR
    TEST_CLAUSE = TEST @Value(_related_suppliers) = 0
    TEST_MODE = TEST
    PASSED -> hydroobject (writer OGCGEOPACKAGE_2)
hydroobject (writer OGCGEOPACKAGE_2)
    attributes: code text(200), globalid text(200), naam text(200), nen3610id text(200)

Bookmark: Stuw
WS_STUWAGGREGATIE (reader ORACLE_SPATIAL_1)
    attributes: OBJECTID number(38,0), CODE nvarchar(50), SOORTSTUW nvarchar(100), LAAGSTEDOORSTROOMHOOGTE number(8,2), HOOGSTEDOORSTROOMHOOGTE number(8,2), HOOGTECONSTRUCTIE number(8,2), DOORSTROOMBREEDTE number(8,2), SOORTREGELBAARHEID nvarchar(100), SOORTMATERIAAL nvarchar(100), WS_MATERIAALREGELCONSTRUCTIE nvarchar(100), WS_STREEFPEIL_ZOMER number(38,10), WS_STREEFPEIL_WINTER number(38,10), WS_STREEFPEILBOVENGRENS number(6,2), WS_STREEFPEIL number(6,2), WS_STREEFPEILONDERGRENS number(6,2), OVERSTORTSTRAAL_Z number(5,0), OVERSTORTSTRAAL_W number(5,0), MAAIVELDHOOGTE number(38,8), REGIMECODE nvarchar(100), PEILBEHEER nvarchar(255), PIEKSITUATIE nvarchar(255), WATERAANVOER nvarchar(255), BIJZONDERHEDEN nvarchar(255), OPMERKING nvarchar(250), STATUSLEGGERWATERSYSTEEM nvarchar(100), STATUSOBJECT nvarchar(100), RICHTING number(5,2), WS_INWINDATUM timestamp(6), SE_ANNO_CAD_DATA blob, WS_ONDERDOORLAAT_JN nvarchar(5),
      STUWID char(38), STATUSLEGGERWATERVEILIGHEID nvarchar(100), VERDEELWERK nvarchar(5)
    -> Clipper_4 [CLIPPEE]
Clipper_4
    BOUNDARY_CASES = Treat as Inside
    CLEANING_TOLERANCE = Automatic
    CLIPPED_ATTR = _clipped
    CLIP_TYPE = Multiple Clippers
    LINES_AS_SEGMENTS = No
    MEASURE_TYPE = Continuous
    MISSING_VAL_MODE = Compute
    PRESERVE_CLIPPEE_EXTENTS = No
    VAL_SOURCE = Clippee Only
    INSIDE -> Tester
Tester
    BOOL_OP = OR
    TEST_CLAUSE = TEST @Value(STATUSOBJECT) = gerealiseerd
    TEST_MODE = TEST
    PASSED -> AttributeCreator_6
AttributeCreator_6
    ATTR_TABLE:
      SET_TO soortstuwcode = FME_CONDITIONAL:DEFAULT_VALUE'99'BOOL_OP;OR;COMPOSITE_TEST;1;TEST @Value(SOORTSTUW) = schotbalkstuw'1'BOOL_OP;OR;COMPOSITE_TEST;1;TEST @Value(SOORTSTUW) = stuw met schuif'2'BOOL_OP;OR;COMPOSITE_TEST;1;TEST @Value(SOORTSTUW) = stuw met klep'3'BOOL_OP;OR;COMPOSITE_TEST;1;TEST @Value(SOORTSTUW) = segmentstuw'4'BOOL_OP;OR;COMPOSITE_TEST;1;TEST @Value(SOORTSTUW) = cascadestuw'5'BOOL_OP;OR;COMPOSITE_TEST;1;TEST @Value(SOORTSTUW) = hevelstuw'6'BOOL_OP;OR;COMPOSITE_TEST;1;TEST @Value(SOORTSTUW) = meetstuw'7'BOOL_OP;OR;COMPOSITE_TEST;1;TEST @Value(SOORTSTUW) = meetschot'8'BOOL_OP;OR;COMPOSITE_TEST;1;TEST @Value(SOORTSTUW) = stuw met contra-gewicht'9'BOOL_OP;OR;COMPOSITE_TEST;1;TEST @Value(SOORTSTUW) = inlaat- en/of aflaatstuw'10'BOOL_OP;OR;COMPOSITE_TEST;1;TEST @Value(SOORTSTUW) = overlaat'11'BOOL_OP;OR;COMPOSITE_TEST;1;TEST @Value(SOORTSTUW) = drijverstuw'12'BOOL_OP;OR;COMPOSITE_TEST;1;TEST @Value(SOORTSTUW) = trommelstuw'13'BOOL_OP;OR;COMPOSITE_TEST;1;TEST @Value(SOORTSTUW) = gronddamstuw'20'BOOL_OP;OR;COMPOSITE_TEST;1;TEST @Value(SOORTSTUW) = stuwbak'21'BOOL_OP;OR;COMPOSITE_TEST;1;TEST @Value(SOORTSTUW) = tuimel- of kantelstuw'22'BOOL_OP;OR;COMPOSITE_TEST;1;TEST @Value(SOORTSTUW) = balgstuw'23'BOOL_OP;OR;COMPOSITE_TEST;1;TEST @Value(SOORTSTUW) = brievenbusstuw'24'BOOL_OP;OR;COMPOSITE_TEST;1;TEST @Value(SOORTSTUW) = knijpstuw'25'BOOL_OP;OR;COMPOSITE_TEST;1;TEST @Value(SOORTSTUW) = conserveringstuw'26'BOOL_OP;OR;COMPOSITE_TEST;1;TEST @Value(SOORTSTUW) = overig'98'FME_NUM_CONDITIONS22___
      SET_TO afvoercoefficient = 1
      SET_TO overlaatonderlaat = FME_CONDITIONAL:DEFAULT_VALUE'Overlaat'BOOL_OP;OR;COMPOSITE_TEST;1;TEST @Value(WS_ONDERDOORLAAT_JN) = Ja'Onderlaat'FME_NUM_CONDITIONS2___
      SET_TO hoogteopening = @Value(HOOGSTEDOORSTROOMHOOGTE)
      SET_TO vormopening = Rechthoekig
      SET_TO hoogstedoorstroombreedte = @Value(DOORSTROOMBREEDTE)
      SET_TO maximalehoogtebovenkant = @Value(HOOGSTEDOORSTROOMHOOGTE)
      SET_TO nen3610id = @Value(CODE)
    -> AttributeRenamer_4
AttributeRenamer_4
    ATTR_TABLE:
      RENAME_SET_DEFAULT CODE > code
      RENAME_SET_DEFAULT DOORSTROOMBREEDTE > laagstedoorstroombreedte
      RENAME_SET_DEFAULT LAAGSTEDOORSTROOMHOOGTE > laagstedoorstroomhoogte
      RENAME_SET_DEFAULT SOORTREGELBAARHEID > soortregelbaarheid
      RENAME_SET_DEFAULT STUWID > stuwid
      RENAME_SET_DEFAULT SOORTSTUW > soortstuw
      RENAME_SET_DEFAULT HOOGSTEDOORSTROOMHOOGTE > hoogstedoorstroomhoogte
    MISSING_INPUT_ATTRS = REMOVE
    -> AttributeCreator_7
    -> UUIDGenerator_4
UUIDGenerator_4
    UUID_ATTR = globalid
    -> kunstwerkopening (writer OGCGEOPACKAGE_2)
    -> AttributeRenamer_12
AttributeRenamer_12
    ATTR_TABLE = RENAME_SET_DEFAULT globalid > kunstwerkopeningid
    MISSING_INPUT_ATTRS = REMOVE
    -> regelmiddel (writer OGCGEOPACKAGE_2)
regelmiddel (writer OGCGEOPACKAGE_2)
    attributes: code text(200), soortregelbaarheid text(200), maximalehoogtebovenkant double, kunstwerkopeningid text(200), overlaatonderlaat text(200), hoogteopening double, duikersifonhevelid text(200), nen3610id text(200)
kunstwerkopening (writer OGCGEOPACKAGE_2)
    attributes: globalid text(200), stuwid text(200), laagstedoorstroombreedte double, laagstedoorstroomhoogte double, hoogstedoorstroombreedte double, hoogstedoorstroomhoogte double, vormopening text(200), afvoercoefficient double, nen3610id text(200)
AttributeCreator_7
    ATTR_TABLE:
      SET_TO globalid = @Value(stuwid)
      SET_TO nen3610id = @Value(code)
    -> stuw (writer OGCGEOPACKAGE_2)
stuw (writer OGCGEOPACKAGE_2)
    attributes: code text(200), globalid text(200), afvoercoefficient double, soortstuw text(200), nen3610id text(200)

Bookmark: Duiker
DUIKERSIFONHEVEL (reader ORACLE_SPATIAL_1)
    attributes: OBJECTID number(38,0), CODE nvarchar(50), HOOGTEBINNENONDERKANTBOV number(8,2), HOOGTEBINNENONDERKANTBENE number(8,2), HOOGTEOPENING number(8,2), BREEDTEOPENING number(8,2), LENGTE number(8,2), VORMKOKER nvarchar(100), SOORTMATERIAAL nvarchar(100), OPMERKING nvarchar(250), HYPERLINK nvarchar(256), WS_HYPERLINKTYPE nvarchar(100), STATUSLEGGERWATERSYSTEEM nvarchar(100), STATUSLEGGERWATERVEILIGHEID nvarchar(100), STATUSOBJECT nvarchar(100), TYPEKRUISING nvarchar(100), WS_INWINDATUM timestamp(6), SE_ANNO_CAD_DATA blob, DUIKERSIFONHEVELID char(38)
    -> Clipper_2 [CLIPPEE]
Clipper_2
    BOUNDARY_CASES = Treat as Inside
    CLEANING_TOLERANCE = Automatic
    CLIPPED_ATTR = _clipped
    CLIP_TYPE = Multiple Clippers
    LINES_AS_SEGMENTS = No
    MEASURE_TYPE = Continuous
    MISSING_VAL_MODE = Compute
    PRESERVE_CLIPPEE_EXTENTS = No
    VAL_SOURCE = Clippee Only
    INSIDE -> Test_Gerealiseerd
Test_Gerealiseerd: Tester
    BOOL_OP = AND
    TEST_CLAUSE = TEST @Value(STATUSOBJECT) = gerealiseerd
    TEST_MODE = TEST
    PASSED -> Vorm_en_ruwheid_toekennen
Note: Omdat vooralsnog alleen ronde en rechthoekige duikers worden ondersteund in D-HYDAMO worden momenteel alle afwijken vormen omgezet naar rond.
Vorm_en_ruwheid_toekennen: AttributeCreator
    ATTR_TABLE = SET_TO ruwheid = FME_CONDITIONAL:DEFAULT_VALUE'75'BOOL_OP;OR;COMPOSITE_TEST;<Unused>;TEST @Value(SOORTMATERIAAL) = asbestcement;TEST @Value(SOORTMATERIAAL) = ijzer;TEST @Value(SOORTMATERIAAL) = staal;TEST @Value(SOORTMATERIAAL) = roestvrij staal'90'BOOL_OP;OR;COMPOSITE_TEST;<Unused>;TEST @Value(SOORTMATERIAAL) = beton;TEST @Value(SOORTMATERIAAL) = gewapend beton;TEST @Value(SOORTMATERIAAL) = overig'75'BOOL_OP;OR;COMPOSITE_TEST;<Unused>;TEST @Value(SOORTMATERIAAL) = gegolfd plaatstaal'30'BOOL_OP;OR;COMPOSITE_TEST;<Unused>;TEST @Value(SOORTMATERIAAL) = metselwerk'50'BOOL_OP;OR;COMPOSITE_TEST;<Unused>;TEST @Value(SOORTMATERIAAL) = hout'65'BOOL_OP;OR;COMPOSITE_TEST;<Unused>;TEST @Value(SOORTMATERIAAL) = kunststof;TEST @Value(SOORTMATERIAAL) = PVC'100'BOOL_OP;OR;COMPOSITE_TEST;<Unused>;TEST @Value(SOORTMATERIAAL) = plaatstaal'55'BOOL_OP;OR;COMPOSITE_TEST;<Unused>;TEST @Value(SOORTMATERIAAL) = gres'60'FME_NUM_CONDITIONS9___
    -> AttributeRenamer_6
AttributeRenamer_6
    ATTR_TABLE:
      RENAME_SET_DEFAULT CODE > code
      RENAME_SET_DEFAULT HOOGTEBINNENONDERKANTBOV > hoogtebinnenonderkantbov
      RENAME_SET_DEFAULT HOOGTEBINNENONDERKANTBENE > hoogtebinnenonderkantbene
      RENAME_SET_DEFAULT HOOGTEOPENING > hoogteopening
      RENAME_SET_DEFAULT BREEDTEOPENING > breedteopening
      RENAME_SET_DEFAULT LENGTE > lengte
      RENAME_SET_DEFAULT VORMKOKER > vormkoker
      RENAME_SET_DEFAULT DUIKERSIFONHEVELID > duikersifonhevelid
    MISSING_INPUT_ATTRS = REMOVE
    -> AttributeCreator_5
AttributeCreator_5
    ATTR_TABLE:
      SET_TO intreeverlies = 1
      SET_TO uittreeverlies = 1
      SET_TO typeruwheid = StricklerKs
      SET_TO nen3610id = @Value(code)
    -> AttributeRenamer_15
AttributeRenamer_15
    ATTR_TABLE = RENAME_SET_DEFAULT duikersifonhevelid > globalid
    MISSING_INPUT_ATTRS = REMOVE
    -> duikersifonhevel (writer OGCGEOPACKAGE_11)
duikersifonhevel (writer OGCGEOPACKAGE_11)
    attributes: code text(200), globalid text(200), hoogtebinnenonderkantbov double, hoogtebinnenonderkantbene double, vormkoker text(200), hoogteopening double, breedteopening double, intreeverlies double, uittreeverlies double, typeruwheid text(200), ruwheid double, lengte double, nen3610id text(200)

Bookmark: Laterals
Laterals (reader FILEGDB_2)
    attributes: OBJECTID objectid, CODE text(50), Opp_hactar double, H_gem double, Maatgevend double, MGA_20_win double, MGA_5_zome double, X single, Y single, NAAM text(250), OPMERKING text(254), Waterloop double
    -> Clipper_5 [CLIPPEE]
Clipper_5
    BOUNDARY_CASES = Treat as Inside
    CLEANING_TOLERANCE = Automatic
    CLIPPED_ATTR = _clipped
    CLIP_TYPE = Multiple Clippers
    LINES_AS_SEGMENTS = No
    MEASURE_TYPE = Continuous
    MISSING_VAL_MODE = Compute
    PRESERVE_CLIPPEE_EXTENTS = No
    VAL_SOURCE = Clippee Only
    INSIDE -> AttributeRenamer_7
AttributeRenamer_7
    ATTR_TABLE:
      RENAME_SET_DEFAULT CODE > code
      RENAME_SET_DEFAULT X > x
      RENAME_SET_DEFAULT Y > y
    MISSING_INPUT_ATTRS = REMOVE
    -> UUIDGenerator_7
UUIDGenerator_7
    UUID_ATTR = globalid
    -> AttributeCreator_16
AttributeCreator_16
    ATTR_TABLE:
      SET_TO nen3610id = @Value(code)
      SET_TO afvoer = @Evaluate(@Value(Maatgevend)/1000)
    -> lateraleknoop (writer OGCGEOPACKAGE_12)
lateraleknoop (writer OGCGEOPACKAGE_12)
    attributes: code text(200), globalid text(200), nen3610id text(200), afvoer text(200)

Bookmark: Gemaal
GEMAAL (reader ORACLE_SPATIAL_1)
    attributes: OBJECTID number(38,0), CODE nvarchar(50), NAAM nvarchar(100), WS_INDICATIEVISPASSEERBAAR nvarchar(5), OPMERKING nvarchar(250), STATUSLEGGERWATERSYSTEEM nvarchar(100), STATUSLEGGERWATERVEILIGHEID nvarchar(100), STATUSOBJECT nvarchar(100), WS_INWINDATUM timestamp(6), SE_ANNO_CAD_DATA blob, GEMAALID char(38)
    -> Clipper_3 [CLIPPEE]
Clipper_3
    BOUNDARY_CASES = Treat as Inside
    CLEANING_TOLERANCE = Automatic
    CLIPPED_ATTR = _clipped
    CLIP_TYPE = Multiple Clippers
    LINES_AS_SEGMENTS = No
    MEASURE_TYPE = Continuous
    MISSING_VAL_MODE = Compute
    PRESERVE_CLIPPEE_EXTENTS = No
    VAL_SOURCE = Clippee Only
    INSIDE -> Test_Gerealiseerd_3
Test_Gerealiseerd_3: Tester
    BOOL_OP = OR
    TEST_CLAUSE = TEST @Value(STATUSOBJECT) = gerealiseerd
    TEST_MODE = TEST
    PASSED -> Kolommen_hernoemen_3
Kolommen_hernoemen_3: AttributeRenamer
    ATTR_LIST = CODE,code,,GEMAALID,gemaalid,
    -> AttributeCreator
AttributeCreator
    ATTR_TABLE:
      SET_TO maximalecapaciteit = 0
      SET_TO streefwaarde = 1
      SET_TO ondergrens = 0
      SET_TO bovengrens = 2
      SET_TO nen3610id = @Value(code)
    -> AttributeRenamer_13
    -> UUIDGenerator_5
    -> UUIDGenerator_6
AttributeRenamer_13
    ATTR_TABLE = RENAME_SET_DEFAULT gemaalid > globalid
    MISSING_INPUT_ATTRS = REMOVE
    -> gemaal (writer OGCGEOPACKAGE_3)
gemaal (writer OGCGEOPACKAGE_3)
    attributes: code text(200), globalid text(200), nen3610id text(200)
UUIDGenerator_6
    UUID_ATTR = globalid
    -> FeatureMerger [REQUESTOR]
UUIDGenerator_5
    UUID_ATTR = globalid
    -> pomp (writer OGCGEOPACKAGE_4)
    -> AttributeRenamer_14
pomp (writer OGCGEOPACKAGE_4)
    attributes: code text(200), globalid text(200), gemaalid text(200), maximalecapaciteit double, nen3610id text(200)
AttributeRenamer_14
    ATTR_TABLE = RENAME_SET_DEFAULT globalid > pompid
    MISSING_INPUT_ATTRS = REMOVE
    -> FeatureMerger [SUPPLIER]
FeatureMerger
    ATTR_ACCUM_MODE = Merge Supplier
    ATTR_CONFLICT_RES = Use Requestor
    IGNORE_NULLS = No
    JOIN_KEYS = @Value(code) @Value(code) AUTO
    MERGE_TYPE = Attributes Only
    PROCESS_DUPS = NO
    REJECT_NULL_MISSING_KEYS = No
    SUPPLIERS_FIRST = No
    MERGED -> sturing (writer OGCGEOPACKAGE_5)
sturing (writer OGCGEOPACKAGE_5)
    attributes: code text(200), globalid text(200), pompid text(200), streefwaarde double, ondergrens double, bovengrens double, nen3610id text(200)

Bookmark: Brug
BRUG (reader ORACLE_SPATIAL_1)
    attributes: OBJECTID number(38,0), CODE nvarchar(50), HOOGTEONDERZIJDE number(8,2), DOORVAARTBREEDTE number(8,2), WS_DOORVAARTLENGTE number(4,2), WS_BODEMHOOGTEBOV number(5,2), SOORTOVERSPANNING nvarchar(100), OPMERKING nvarchar(250), HYPERLINK nvarchar(500), WS_HYPERLINKTYPE nvarchar(100), STATUSLEGGERWATERSYSTEEM nvarchar(100), STATUSOBJECT nvarchar(100), RICHTING number(5,2), WS_INWINDATUM timestamp(6), SE_ANNO_CAD_DATA blob, BRUGID char(38)
    -> Clipper [CLIPPEE]
Clipper
    BOUNDARY_CASES = Treat as Inside
    CLEANING_TOLERANCE = Automatic
    CLIPPED_ATTR = _clipped
    CLIP_TYPE = Multiple Clippers
    LINES_AS_SEGMENTS = No
    MEASURE_TYPE = Continuous
    MISSING_VAL_MODE = Compute
    PRESERVE_CLIPPEE_EXTENTS = No
    VAL_SOURCE = Clippee Only
    INSIDE -> Test_Gerealiseerd_2
Test_Gerealiseerd_2: Tester
    BOOL_OP = OR
    TEST_CLAUSE = TEST @Value(STATUSOBJECT) = gerealiseerd
    TEST_MODE = TEST
    PASSED -> AttributeRenamer_code_brugid
AttributeRenamer_code_brugid
    ATTR_TABLE:
      RENAME_SET_DEFAULT CODE > code
      RENAME_SET_DEFAULT BRUGID > brugid
    MISSING_INPUT_ATTRS = REMOVE
    -> AttributeCreator_nen3610id_2
AttributeCreator_nen3610id_2
    ATTR_TABLE = SET_TO nen3610id = @Value(code)
    -> globalid_2
    -> AttributeRenamer_5
globalid_2: UUIDGenerator
    UUID_ATTR = globalid
    -> profielgroep (writer OGCGEOPACKAGE_6)
    -> CoordinateExtractor
CoordinateExtractor
    IND = 0
    MODE = Specify Coordinate
    X_ATTR = _x
    Y_ATTR = _y
    -> AttributeCreator_9
AttributeCreator_9
    ATTR_TABLE:
      SET_TO z_onder = @Value(WS_BODEMHOOGTEBOV)
      SET_TO xlinks = @Evaluate(@Value(_x)-(@Value(DOORVAARTBREEDTE)/2))
      SET_TO xrechts = @Evaluate(@Value(_x)+(@Value(DOORVAARTBREEDTE)/2))
      SET_TO z_boven = @Value(HOOGTEONDERZIJDE)
    -> Creeer_punt_linksonder
    -> Creeer_punt_rechtsonder
    -> Creeer_punt_linksboven
    -> Creeer_punt_rechtsboven
Creeer_punt_linksboven: VertexCreator
    MEASURE_TYPE = Continuous
    MODE_NAME = Replace with Point
    XVAL = @Value(xlinks)
    YVAL = @Value(_y)
    ZVAL = @Value(z_boven)
    -> AttributeCreator_13
    -> LineBuilder
AttributeCreator_13
    ATTR_TABLE = SET_TO codevolgnummer = 1
    -> AttributeCreator_10
Creeer_punt_rechtsboven: VertexCreator
    MEASURE_TYPE = Continuous
    MODE_NAME = Replace with Point
    XVAL = @Value(xrechts)
    YVAL = @Value(_y)
    ZVAL = @Value(z_boven)
    -> AttributeCreator_14
    -> LineBuilder
LineBuilder
    ACCUM_INPUT_ATTRS = Use Attributes From One Feature
    GROUP_BY = code
    REMOVE_DUPLICATES = No
    LINE -> AttributeRenamer_16
AttributeRenamer_16
    ATTR_TABLE = RENAME_SET_DEFAULT globalid > profielgroepid
    MISSING_INPUT_ATTRS = REMOVE
    -> globalid_3
globalid_3: UUIDGenerator
    UUID_ATTR = globalid
    UUID_FORMAT = UUID_ONLY
    -> profiellijn (writer OGCGEOPACKAGE_7)
    -> FeatureMerger_3 [SUPPLIER]
AttributeCreator_14
    ATTR_TABLE = SET_TO codevolgnummer = 4
    -> AttributeCreator_10
Creeer_punt_rechtsonder: VertexCreator
    MEASURE_TYPE = Continuous
    MODE_NAME = Replace with Point
    XVAL = @Value(xrechts)
    YVAL = @Value(_y)
    ZVAL = @Value(z_onder)
    -> AttributeCreator_12
AttributeCreator_12
    ATTR_TABLE = SET_TO codevolgnummer = 3
    -> AttributeCreator_10
Note: Omdat in D-HYDAMO het type 'rectangle' voor bruggen niet wordt ondersteund worden de doorstroombreedte en doorstroomhoogte vertaald naar profielpunten.
Creeer_punt_linksonder: VertexCreator
    MEASURE_TYPE = Continuous
    MODE_NAME = Replace with Point
    XVAL = @Value(xlinks)
    YVAL = @Value(_y)
    ZVAL = @Value(z_onder)
    -> AttributeCreator_11
AttributeCreator_11
    ATTR_TABLE = SET_TO codevolgnummer = 2
    -> AttributeCreator_10
AttributeCreator_10
    ATTR_TABLE:
      SET_TO typeprofielcode = 4
      SET_TO typeruwheid = StricklerKs
      SET_TO ruwheidlaag = 75
      SET_TO ruwheidhoog = 75
      SET_TO codegerelateerdobject = @Value(code)
    -> AttributeRemover_globalid
AttributeRemover_globalid
    REMOVE_ATTRS = globalid
    -> FeatureMerger_3 [REQUESTOR]
FeatureMerger_3
    ATTR_ACCUM_MODE = Merge Supplier
    ATTR_CONFLICT_RES = Use Requestor
    IGNORE_NULLS = No
    JOIN_KEYS = @Value(code) @Value(code) AUTO
    MERGE_TYPE = Attributes Only
    PROCESS_DUPS = NO
    REJECT_NULL_MISSING_KEYS = No
    SUPPLIERS_FIRST = No
    MERGED -> AttributeRenamer_profiellijnid
AttributeRenamer_profiellijnid
    ATTR_TABLE = RENAME_SET_DEFAULT globalid > profiellijnid
    MISSING_INPUT_ATTRS = REMOVE
    -> UUIDGenerator_globalid_2
AttributeRenamer_5
    ATTR_TABLE:
      RENAME_SET_DEFAULT WS_DOORVAARTLENGTE > lengte
      RENAME_SET_DEFAULT WS_BODEMHOOGTEBOV > hoogteonderzijde
      RENAME_SET_DEFAULT HOOGTEONDERZIJDE > hoogtebovenzijde
      RENAME_SET_DEFAULT brugid > globalid
    MISSING_INPUT_ATTRS = REMOVE
    -> AttributeCreator_4
AttributeCreator_4
    ATTR_TABLE:
      SET_TO typeruwheid = StricklerKs
      SET_TO ruwheid = 75
      SET_TO intreeverlies = 1
      SET_TO uittreeverlies = 1
    -> brug (writer OGCGEOPACKAGE_10)
brug (writer OGCGEOPACKAGE_10)
    attributes: code text(200), globalid text(200), lengte double, typeruwheid text(200), ruwheid double, intreeverlies double, uittreeverlies double, nen3610id text(200)
